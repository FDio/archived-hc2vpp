module sample-plugin {

    yang-version 1;
    namespace "http://fd.io/hc2vpp/yang/sample-plugin";
    prefix "samples";

    import ietf-inet-types {
        prefix "inet";
    }

    organization
        "FD.io - The Fast Data Project";

    contact
        "Hc2vpp Wiki <https://wiki.fd.io/view/Hc2vpp>
         Mailing List <hc2vpp@lists.fd.io>";

    description
        "Sample model for demonstration of translation code.

         Copyright (c) 2016 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision 2016-12-14 {
        description "Sample model for demonstration of transation code";
    }

    grouping sample-plugin-params {
        container vxlans {
            list vxlan-tunnel {

                key id;
                leaf id {
                    type string;
                }

                leaf src {
                  type inet:ip-address;
                }
                leaf dst {
                  type inet:ip-address;
                }
            }
        }
    }

    container sample-plugin-state {
        config false;
        uses sample-plugin-params;
    }

    container sample-plugin {
        uses sample-plugin-params;
    }
}
