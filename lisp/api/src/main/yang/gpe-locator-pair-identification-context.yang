module gpe-locator-pair-identification-context {
    yang-version 1;
    namespace "urn:honeycomb:params:xml:ns:yang:gpe:locator:pair:identification:context";
    prefix "gpe-locator-pair-identification-context";

    description
            "This module contains mappings between gpe entry identificator and locator pair in vpp";

    revision "2017-05-17" {
        description
            "Initial revision.";
    }

    import lisp {prefix "lisp";}
    import ietf-inet-types {prefix "inet";}
    import yang-ext {prefix "ext";}
    import naming-context { prefix "nc";}

    grouping gpe-locator-pair-identification-context-attributes{

        container gpe-locator-pair-identification-contexts {

            list gpe-locator-pair-identification {

                key "name";

                leaf name {
                    type string;
                }

                container mappings{
                    list mapping {

                        key "id";

                        leaf id {
                          type string;
                          description "Id that uniquely identifies gpe entry";
                        }

                        list locator-pair-mapping {
                            key "id";

                            leaf id {
                              type string;
                              description "Id that uniquely identifies locator pair";
                            }

                            container pair {
                                leaf local-address{
                                  type inet:ip-address;
                                  description "Local locator address";
                                }
                                leaf remote-address {
                                  type inet:ip-address;
                                  description "Remote locator address";
                                }
                            }
                        }
                    }
                }
            }
        }
    }

     augment /nc:contexts {
            ext:augment-identifier "gpe-locator-pair-identification-ctx-augmentation";
            uses gpe-locator-pair-identification-context-attributes;
     }
}
