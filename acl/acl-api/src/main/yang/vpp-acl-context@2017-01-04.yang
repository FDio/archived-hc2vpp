module vpp-acl-context {
    yang-version 1;
    namespace "http://fd.io/hc2vpp/yang/vpp/acl/context";
    prefix "vac";

    import naming-context {
        prefix "nc";
    }

    import yang-ext {
        prefix "ext";
    }

    organization
        "FD.io - The Fast Data Project";

    contact
        "Hc2vpp Wiki <https://wiki.fd.io/view/Hc2vpp>
         Mailing List <hc2vpp@lists.fd.io>";

    description
        "This module provides mapping between ACL identifiers
         defined in the ietf-access-control-list module
         and identifiers used by the VPP ACL plugin.

         The mapping is managed internally by the HC ACL plugin.
         It is exposed as operational state data for debugging purposes.

         Copyright (c) 2017 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision "2017-01-04" {
        description "Initial revision.";
    }

    grouping vpp-acl-context-attributes {
        container vpp-acl-mappings {
            list vpp-acl-context {

                key "name";

                leaf name {
                    type string;
                    description "vpp-acl context name";
                }

                list acl-mapping {
                    key "name";

                    leaf name {
                        type string;
                        description "ACL name";
                    }

                    leaf index {
                        type int32;
                        description "ACL index";
                    }

                    list ace-mapping {
                        key "name";

                        leaf name {
                            type string;
                            description "ACEs name";
                        }

                        leaf index {
                            type int32;
                            description "ACE index";
                        }
                    }
                }
            }
        }
    }

    augment /nc:contexts {
        ext:augment-identifier "vpp-acl-context-augmentation";
        uses vpp-acl-context-attributes;
    }
}
