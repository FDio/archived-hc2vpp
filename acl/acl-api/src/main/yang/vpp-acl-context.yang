module vpp-acl-context {
    yang-version 1;
    namespace "urn:opendaylight:params:xml:ns:yang:vpp:acl:context";
    prefix "nc";

    description "Context for vpp-acl assignment mapping";

    revision "2017-01-04" {
        description "Initial revision.";
    }

    import naming-context {
        prefix "nc";
    }

    import yang-ext {
        prefix "ext";
    }

    grouping vpp-acl-context-attributes {
        container vpp-acl-mappings {
            list vpp-acl-context {

                key "name";

                leaf name {
                    type string;
                    description "vpp-acl context name";
                }

                list acl-mapping {
                    key "name";

                    leaf name {
                        type string;
                        description "ACL name";
                    }

                    leaf index {
                        type int32;
                        description "ACL index";
                    }

                    list ace-mapping {
                        key "name";

                        leaf name {
                            type string;
                            description "ACEs name";
                        }

                        leaf index {
                            type int32;
                            description "ACE index";
                        }
                    }
                }
            }
        }
    }

    augment /nc:contexts {
        ext:augment-identifier "vpp-acl-context-augmentation";
        uses vpp-acl-context-attributes;
    }
}
