module vpp-jvpp-cfg {
    yang-version 1;
    namespace "urn:honeycomb:params:xml:ns:yang:vpp:jvpp:cfg";
    prefix "vjvppc";

    import config { prefix config; revision-date 2013-04-05; }

    description
        "This module contains the base YANG definitions for
         readers/writers plugged into a honeycomb";

    revision "2016-04-06" {
        description
            "Initial revision.";
    }

    identity vpp-jvpp {
        base "config:service-type";
        config:java-class org.openvpp.jvpp.future.FutureJVpp;
    }

    identity vpp-jvpp-impl {
        base config:module-type;
        config:provided-service vpp-jvpp;
    }

    augment "/config:modules/config:module/config:configuration" {
        case vpp-jvpp-impl {
            when "/config:modules/config:module/config:type = 'vpp-jvpp-impl'";

            leaf name {
                type string;
                default "v3poODL";
            }

            leaf description {
                type string;
                description "Artificial leaf just to trigger reinitialization of JVpp from HC";
            }
        }
    }

}
