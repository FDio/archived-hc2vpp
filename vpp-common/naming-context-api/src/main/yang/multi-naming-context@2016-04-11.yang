module multi-naming-context {
    yang-version 1;
    namespace "http://fd.io/hc2vpp/yang/multi-naming-context";
    prefix "mnc";

    import naming-context {
       prefix "nc";
    }

    import yang-ext {
       prefix "ext";
    }

    organization
        "FD.io - The Fast Data Project";

    contact
        "Hc2vpp Wiki <https://wiki.fd.io/view/Hc2vpp>
         Mailing List <hc2vpp@lists.fd.io>";

    description
        "This module contains data definition for naming multi-mapping context.

         Multi-naming context provides one-to-many mapping
         between string names used in YANG models and integer indices used by VPP.

         The mapping is managed internally by the HC plugins.
         It is exposed as operational state data for debugging purposes.

         Copyright (c) 2016 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision "2016-04-11" {
        description
            "Initial revision.";
    }

    grouping multi-naming-contexts-attributes {
        container multi-naming-contexts {
            config false;
            // context data

            list multi-naming {

                key "name";

                leaf name {
                    type string;
                }

                container mappings {
                    list mapping {

                        key "name";

                        leaf name {
                            type string;
                        }

                        list value {
                            key "name";

                            unique "index";
                            leaf index {
                                type int32;
                            }

                            leaf name {
                                type string;
                            }
                        }
                    }
                }
            }
        }
    }

    augment /nc:contexts {
        ext:augment-identifier "multi-mapping-ctx-augmentation";
        uses multi-naming-contexts-attributes;
    }
}
