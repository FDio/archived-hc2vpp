module naming-context {
    yang-version 1;
    namespace "http://fd.io/hc2vpp/yang/naming-context";
    prefix "nc";

    organization
        "FD.io - The Fast Data Project";

    contact
        "Hc2vpp Wiki <https://wiki.fd.io/view/Hc2vpp>
         Mailing List <hc2vpp@lists.fd.io>";

    description
        "This module contains data definition for naming mapping context.

         Naming context provides one-to-one mapping
         between string names used in YANG models and integer indices used by VPP.

         The mapping is managed internally by the HC plugins.
         It is exposed as operational state data for debugging purposes.

         Copyright (c) 2016 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision "2016-05-13" {
        description
            "Initial revision.";
    }

    container contexts {
        config false;
        // context data

        list naming-context {

            key "name";

            leaf name {
                type string;
            }

            container mappings {
                list mapping {

                    key "name";
                    unique "index";

                    leaf name {
                        type string;
                    }

                    leaf index {
                        type int32;
                    }
                }
            }
        }
    }
}
