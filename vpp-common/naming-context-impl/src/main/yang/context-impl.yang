module context-impl {
    yang-version 1;
    namespace "urn:opendaylight:params:xml:ns:yang:context:impl";
    prefix "v3po-impl";

    import config { prefix config; revision-date 2013-04-05; }
    import opendaylight-md-sal-binding { prefix md-sal-binding; revision-date 2013-10-28;}
    import translate-api { prefix tapi; revision-date 2016-04-06; }

    description
        "Service definition for v3po project";

    revision "2014-12-10" {
        description
            "Initial revision";
    }

    identity context-reader {
        base config:module-type;
        config:provided-service tapi:honeycomb-reader-factory;
        description "A reader to provide naming context related data";
    }

    augment "/config:modules/config:module/config:configuration" {
        case context-reader {
            when "/config:modules/config:module/config:type = 'context-reader'";

            container context-binding-broker {
                uses config:service-ref {
                    refine type {
                        mandatory true;
                        config:required-identity md-sal-binding:binding-async-data-broker;
                    }
                }
            }

        }
    }
}
