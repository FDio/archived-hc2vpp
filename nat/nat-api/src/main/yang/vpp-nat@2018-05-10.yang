module vpp-nat {
  yang-version 1;
  namespace "http://fd.io/hc2vpp/yang/vpp-nat";
  prefix "vpp-nat";

  import ietf-nat {
    prefix "nat";
  }
  import yang-ext {
    prefix "ext";
  }

  organization
    "FD.io - The Fast Data Project";

  contact
    "Hc2vpp Wiki <https://wiki.fd.io/view/Hc2vpp>
     Mailing List <hc2vpp@lists.fd.io>";

  description
    "This module contains a collection of YANG definitions that extend ietf-nat module
     with VPP specific features provided by the VPP NAT plugin.

     Copyright (c) 2018 Cisco and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision "2018-05-10" {
    description "Adapt to ietf-nat@2018-02-23.";
  }

  revision "2017-08-04" {
    description "Initial revision of vpp-nat model.";
  }

  typedef nat-pool-type {
    type enumeration {
      enum "nat44";
      enum "nat64";
    }
  }

  grouping external-ip-address-pool-vpp-attributes {
    leaf pool-type {
      type nat-pool-type;
      description
        "Indicates whether the pool is designated to be used for nat44 or nat64.";
      reference
        "https://git.fd.io/vpp/tree/src/plugins/nat/nat.api";
    }
  }

  augment /nat:nat/nat:instances/nat:instance/nat:policy/nat:external-ip-address-pool {
    ext:augment-identifier "external-ip-address-pool-augmentation";

    uses external-ip-address-pool-vpp-attributes;
  }
}
