module subinterface-nat {
  yang-version 1;
  namespace "http://fd.io/hc2vpp/yang/subinterface-nat";
  prefix "sub-ifc-nat";

  import ietf-interfaces {
    prefix "if";
  }
  import vpp-vlan {
    prefix "vpp-vlan";
  }
  import interface-nat {
    prefix "ifc-nat";
  }
  import yang-ext {
    prefix "ext";
  }

  organization
    "FD.io - The Fast Data Project";

  contact
    "Hc2vpp Wiki <https://wiki.fd.io/view/Hc2vpp>
     Mailing List <hc2vpp@lists.fd.io>";

  description
    "This module contains a collection of YANG definitions for
     applying NAT configuration on VPP subinterfaces.

     Copyright (c) 2017 Cisco and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision "2017-06-15" {
    description "Initial revision of subinterface-nat model";
  }

  augment /if:interfaces/if:interface/vpp-vlan:sub-interfaces/vpp-vlan:sub-interface {
    ext:augment-identifier "nat-subinterface-augmentation";

    uses ifc-nat:interface-nat-attributes;
  }
}
