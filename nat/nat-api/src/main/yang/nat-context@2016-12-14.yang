module nat-context {
    yang-version 1;
    namespace "http://fd.io/hc2vpp/yang/nat-context";
    prefix "nat-ctx";

    import ietf-inet-types {
       prefix "inet";
    }

    import naming-context {
       prefix "nc";
    }

    import yang-ext {
       prefix "ext";
    }

    organization
        "FD.io - The Fast Data Project";

    contact
        "Hc2vpp Wiki <https://wiki.fd.io/view/Hc2vpp>
         Mailing List <hc2vpp@lists.fd.io>";

    description
        "This module provides mapping between NAT identifiers
         defined in the ietf-nat module
         and identifiers used by the VPP NAT plugin.

         The mapping is managed internally by the HC NAT plugin.
         It is exposed as operational state data for debugging purposes.

         Copyright (c) 2016 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision "2016-12-14" {
        description "Initial revision.";
    }

    grouping mapping-entry-context-attributes {
        container nat-mapping-entry-context {
            list nat-instance {
                key "id";

                leaf id {
                    type uint32;
                    description "ID of the NAT instance from ietf-nat. Maps to VRF-ID in VPP";
                }

                container mapping-table {
                    list mapping-entry {

                        key "internal external";
                        unique "index";

                        leaf internal {
                            type inet:ip-prefix;
                            description "Local IP address set in VPP";
                        }

                        leaf external {
                            type inet:ip-prefix;
                            description "Extarnal IP address set in VPP";
                        }

                        leaf index {
                            type uint32;
                            description "ID of the NAT's mapping entry from ietf-nat";
                        }
                    }
                }
            }
        }
    }

    augment /nc:contexts {
        ext:augment-identifier "nat-mapping-entry-ctx-augmentation";
        uses mapping-entry-context-attributes;
    }
}
