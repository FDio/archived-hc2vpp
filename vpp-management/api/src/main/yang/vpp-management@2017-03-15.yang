module vpp-management {
  yang-version 1;
  namespace "http://fd.io/hc2vpp/yang/vpp-management";
  prefix "vpp-m";

  organization
    "FD.io - The Fast Data Project";

  contact
    "Hc2vpp Wiki <https://wiki.fd.io/view/Hc2vpp>
     Mailing List <hc2vpp@lists.fd.io>";

  description
    "This module contains a collection of YANG definitions
     that expose VPP operational state.

     Copyright (c) 2017 Cisco and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision "2017-03-15" {
    description
      "This revision add support for
         - Vpp state attributes read
         - RPC cli support";
  }

  container vpp-state {
    config false;

    description
      "VPP operational data";

    container version {
      leaf name {
        type string;
      }
      leaf build-directory {
        type string;
      }
      leaf build-date {
        type string;
      }
      leaf branch {
        type string;
      }
      leaf pid {
        type uint32;
        description
          "PID of the vpp process";
      }
      description
        "vlib version info";
    }
  }

  rpc cli-inband {
    input {
      leaf cmd {
        type string;
      }
    }
    output {
      leaf reply {
        type string;
      }
    }
  }
}
