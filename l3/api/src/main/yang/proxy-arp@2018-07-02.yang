module proxy-arp {
  yang-version 1;
  namespace "urn:opendaylight:params:xml:ns:yang:vpp:proxy:arp";
  prefix "proxy-arp";

  import ietf-inet-types {
    prefix "inet";
  }
  import ietf-interfaces {
    prefix "if";
  }
  import yang-ext {
    prefix "ext";
  }
  import vpp-fib-table-management {
    prefix fib-management;
    revision-date 2018-05-21;
  }

  organization
    "FD.io - The Fast Data Project";

  contact
    "Hc2vpp Wiki <https://wiki.fd.io/view/Hc2vpp>
     Mailing List <hc2vpp@lists.fd.io>";

  description
    "This module contains a collection of YANG definitions for
     managing Proxy ARP in VPP.

     Copyright (c) 2017 Cisco and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision "2018-07-02" {
    description
      "Uses references to vrf-management module insted of table identifiers.";
    reference
      "https://jira.fd.io/browse/HC2VPP-317";
  }

  revision "2017-03-15" {
    description "Initial revision of proxy ARP model for VPP";
  }

  container proxy-ranges {
    list proxy-range {
      key "vrf-id low-addr high-addr";
      leaf vrf-id {
        type fib-management:fib-table-list-ref;
      }
      leaf low-addr {
        type inet:ipv4-address;
      }
      leaf high-addr {
        type inet:ipv4-address;
      }
      description
        "Parameters for configuring Proxy ARP on interfaces.";
    }
  }

  augment /if:interfaces/if:interface {
    ext:augment-identifier "proxy-arp-interface-augmentation";

    container proxy-arp {
      presence "Enables proxy ARP on given interface";
    }
  }

  // TODO(HC2VPP-86): add interfaces-state augmentation once VPP supports ARP proxy read (VPP-225)
}
