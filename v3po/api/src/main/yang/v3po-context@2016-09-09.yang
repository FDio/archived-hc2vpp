module v3po-context {
  yang-version 1;
  namespace "http://fd.io/hc2vpp/yang/v3po-context";
  prefix "v3po-ctx";

  organization
    "FD.io - The Fast Data Project";

  contact
    "Hc2vpp Wiki <https://wiki.fd.io/view/Hc2vpp>
     Mailing List <hc2vpp@lists.fd.io>";

  description
    "This module contains data definition for v3po module metadata.

     Copyright (c) 2016 Cisco and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision "2016-09-09" {
    description
    "Initial revision of v3po specific context";
  }

  container disabled-interfaces {
    config false;
    // context data

    description "Index list of disabled interfaces. VPP does not always delete an interface after deletion. It just
                 disables it and keeps it there. Honeycomb can hide such interfaces from operational data, and this
                 is the place to heep track of which interfaces were deleted, but are expected to show up in VPP";

    list disabled-interface-index {

        key "index";

        leaf index {
            type int32;
        }
    }
  }

}
