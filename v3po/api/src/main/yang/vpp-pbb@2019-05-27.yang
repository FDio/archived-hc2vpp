module vpp-pbb {
  yang-version 1;
  namespace "http://fd.io/hc2vpp/yang/vpp-pbb";
  prefix "vpp-pbb";

  import ietf-interfaces {
    prefix "if";
  }

  import pbb-types {
    prefix "pbb-types";
  }

  import yang-ext {
    prefix "ext";
  }

  organization
    "FD.io - The Fast Data Project";

  contact
    "Hc2vpp Wiki <https://wiki.fd.io/view/Hc2vpp>
     Mailing List <hc2vpp@lists.fd.io>";

  description
    "This module contains a collection of YANG definitions
     that extend ietf-interfaces module
     with support for PBB based subinterfaces.

     Copyright (c) 2016 Cisco and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision "2019-05-27" {
    description
      "Removed interfaces-state augmentations due to its deprecation
       in ietf-interfaces model";
  }

  revision "2016-12-14" {
    description "Initial revision of pbb model";
  }

  augment /if:interfaces/if:interface {
     ext:augment-identifier "pbb-rewrite-interface-augmentation";
     container pbb-rewrite {
        uses pbb-types:pbb-rewrite-attributes;
     }
  }
}
