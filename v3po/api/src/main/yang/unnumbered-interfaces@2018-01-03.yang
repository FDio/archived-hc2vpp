module unnumbered-interfaces {
  yang-version 1;
  namespace "http://fd.io/hc2vpp/yang/unnumbered-interfaces";
  prefix "uni";

  import ietf-interfaces {
    prefix "if";
  }

  import vpp-vlan {
    prefix "vpp-vlan";
  }

  import yang-ext {
    prefix "ext";
  }

  organization
    "FD.io - The Fast Data Project";

  contact
    "Hc2vpp Wiki <https://wiki.fd.io/view/Hc2vpp>
     Mailing List <hc2vpp@lists.fd.io>";

  description
    "This module contains a collection of YANG definitions
     providing IP unnumbered feature for VPP interfaces and subinterfaces.

     Copyright (c) 2017-2018 Cisco and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision "2018-01-03" {
    description
      "Use if:interface-ref for name of the interface which provides IP.";
  }

  revision "2017-05-10" {
    description
      "Initialial revision";
  }

  grouping unnumbered-config-attributes {
    container unnumbered {
      presence "Sets interface as unnumbered";
      leaf use {
        type if:interface-ref;
        mandatory true;
        description
          "Name of interface or subinterface which IP is to be borrowed.";
      }
    }
  }

  augment /if:interfaces/if:interface {
    ext:augment-identifier "interface-unnumbered-augmentation";
    uses unnumbered-config-attributes;
  }

  augment /if:interfaces/if:interface/vpp-vlan:sub-interfaces/vpp-vlan:sub-interface {
    ext:augment-identifier "subinterface-unnumbered-augmentation";
    uses unnumbered-config-attributes;
  }
}
