module subinterface-span {
  yang-version 1;
  namespace "http://fd.io/hc2vpp/yang/subinterface-span";
  prefix "subif-span";

  import ietf-interfaces {
    prefix "if";
  }

  import vpp-vlan {
    prefix "vpp-vlan";
  }

  import yang-ext {
    prefix "ext";
  }

  import v3po {
    prefix "v3po";
  }

  organization
    "FD.io - The Fast Data Project";

  contact
    "Hc2vpp Wiki <https://wiki.fd.io/view/Hc2vpp>
     Mailing List <hc2vpp@lists.fd.io>";

  description
    "This model contains a collection of YANG definitions for
     span interface management in VPP.

     Copyright (c) 2017 Cisco and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision "2017-06-07" {
    description "Eliminated config leafrefs in operational tree";
  }

  revision "2017-05-10" {
    description
      "Initialial revision that adds support for mirroring interfaces on subinterfaces.
       Vpp implementation allows/implements only two cases:
        - Src: interface |Dst: interface - covered in v3po.yang
        - Src: interface |Dst: subinterface - covered by this model";
  }

  augment /if:interfaces/if:interface/vpp-vlan:sub-interfaces/vpp-vlan:sub-interface {
    ext:augment-identifier "vpp-subinterface-span-augmentation";
    container span {
      uses v3po:span-attributes;
    }
  }
}
