module data-api {
    yang-version 1;
    namespace "urn:honeycomb:params:xml:ns:yang:data:api";
    prefix "dapi";

    import config { prefix config; revision-date 2013-04-05; }

    description
        "This module contains the base YANG data tree definitions
        for data store modeling";

    revision "2016-04-11" {
        description
            "Initial revision.";
    }

    identity data-tree {
        base "config:service-type";
        config:java-class org.opendaylight.yangtools.yang.data.api.schema.tree.DataTree;
    }

    identity honeycomb-readable-data-tree {
        base "config:service-type";
        config:java-class io.fd.honeycomb.v3po.data.ReadableDataManager;
    }

    identity honeycomb-modifiable-data-tree {
        base "config:service-type";
        config:java-class io.fd.honeycomb.v3po.data.ModifiableDataManager;
    }

    typedef datatree-type {
        type enumeration {
             enum config;
             enum oper;
         }
    }
}
