module translate-api {
    yang-version 1;
    namespace "urn:honeycomb:params:xml:ns:yang:translate:api";
    prefix "tapi";

    import config { prefix config; revision-date 2013-04-05; }

    description
        "This module contains the base YANG definitions for
         readers/writers plugged into a honeycomb";

    revision "2016-04-06" {
        description
            "Initial revision.";
    }

    identity honeycomb-reader-factory {
        base "config:service-type";
        config:java-class io.fd.honeycomb.v3po.translate.read.ReaderFactory;
    }

    identity honeycomb-reader-registry {
        base "config:service-type";
        config:java-class io.fd.honeycomb.v3po.translate.read.registry.ModifiableReaderRegistryBuilder;
    }

    identity honeycomb-reader-registry-builder {
        base "config:service-type";
        config:java-class io.fd.honeycomb.v3po.translate.read.registry.ReaderRegistryBuilder;
    }

    identity honeycomb-writer-factory {
        base "config:service-type";
        config:java-class io.fd.honeycomb.v3po.translate.write.WriterFactory;
    }

    identity honeycomb-writer-registry {
        base "config:service-type";
        config:java-class io.fd.honeycomb.v3po.translate.write.registry.ModifiableWriterRegistryBuilder;
    }

    identity honeycomb-writer-registry-builder {
        base "config:service-type";
        config:java-class io.fd.honeycomb.v3po.translate.write.registry.WriterRegistryBuilder;
    }

    identity honeycomb-mapping-context {
        base "config:service-type";
        config:java-class io.fd.honeycomb.v3po.translate.MappingContext;
    }

}
