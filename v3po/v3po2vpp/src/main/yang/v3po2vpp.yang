module v3po2vpp {
    yang-version 1;
    namespace "urn:honeycomb:params:xml:ns:yang:v3po2vpp";
    prefix "v3po2vpp";

    import config { prefix config; revision-date 2013-04-05; }
    import translate-api { prefix tapi; revision-date 2016-04-06; }
    import vpp-jvpp-cfg { prefix vjvppc; revision-date 2016-04-06; }
    import cfg-init { prefix init; revision-date "2016-04-07"; }
    import opendaylight-md-sal-binding { prefix md-sal-binding; revision-date 2013-10-28;}
    import vpp-util { prefix vpp-u; revision-date 2016-04-06; }
    import threadpool {prefix th;}
    import notification-api { prefix hc-notif-a; revision-date 2016-06-01; }

    description
        "This module contains reads and writers for v3po yang model";

    revision "2016-04-06" {
        description
            "Initial revision.";
    }

    identity vpp-state-honeycomb-reader {
        base config:module-type;
        config:provided-service tapi:honeycomb-reader-factory;
    }

    augment "/config:modules/config:module/config:configuration" {
        case vpp-state-honeycomb-reader {
            when "/config:modules/config:module/config:type = 'vpp-state-honeycomb-reader'";

            container vpp-jvpp {
                uses config:service-ref {
                    refine type {
                        mandatory true;
                        config:required-identity vjvppc:vpp-jvpp;
                    }
                }
            }

            container interface-context-vpp-state {
                uses config:service-ref {
                    refine type {
                        mandatory true;
                        config:required-identity vpp-u:naming-context;
                    }
                }
            }

            container bridge-domain-context-vpp-state {
                uses config:service-ref {
                    refine type {
                        mandatory true;
                        config:required-identity vpp-u:naming-context;
                    }
                }
            }

            container keepalive-executor {
                uses config:service-ref {
                    refine type {
                        mandatory true;
                        config:required-identity th:scheduled-threadpool;
                    }
                }

                description "Used to schedule keepalives";
            }
        }
    }

    identity vpp-interface-notification-producer {
        base config:module-type;
        config:provided-service hc-notif-a:honeycomb-notification-producer;
    }

    augment "/config:modules/config:module/config:configuration" {
        case vpp-interface-notification-producer {
            when "/config:modules/config:module/config:type = 'vpp-interface-notification-producer'";

            container vpp-jvpp {
                uses config:service-ref {
                    refine type {
                        mandatory true;
                        config:required-identity vjvppc:vpp-jvpp;
                    }
                }
            }

            container interface-context {
                uses config:service-ref {
                    refine type {
                        mandatory true;
                        config:required-identity vpp-u:naming-context;
                    }
                }
            }

            container realtime-mapping-context {
                uses config:service-ref {
                    refine type {
                        mandatory true;
                        config:required-identity tapi:honeycomb-mapping-context;
                    }
                }
            }
        }
    }

    identity interfaces-state-honeycomb-reader {
        base config:module-type;
        config:provided-service tapi:honeycomb-reader-factory;
    }

    augment "/config:modules/config:module/config:configuration" {
        case interfaces-state-honeycomb-reader {
            when "/config:modules/config:module/config:type = 'interfaces-state-honeycomb-reader'";

            container vpp-jvpp {
                uses config:service-ref {
                    refine type {
                        mandatory true;
                        config:required-identity vjvppc:vpp-jvpp;
                    }
                }
            }

            container interface-context-ifc-state {
                uses config:service-ref {
                    refine type {
                        mandatory true;
                        config:required-identity vpp-u:naming-context;
                    }
                }
            }

            container bridge-domain-context-ifc-state {
                uses config:service-ref {
                    refine type {
                        mandatory true;
                        config:required-identity vpp-u:naming-context;
                    }
                }
            }

            container classify-table-context {
                uses config:service-ref {
                    refine type {
                        mandatory true;
                        config:required-identity vpp-u:naming-context;
                    }
                }
            }

        }
    }

    identity vpp-classifier-state-honeycomb-reader {
        base config:module-type;
        config:provided-service tapi:honeycomb-reader-factory;
    }

    augment "/config:modules/config:module/config:configuration" {
        case vpp-classifier-state-honeycomb-reader {
            when "/config:modules/config:module/config:type = 'vpp-classifier-state-honeycomb-reader'";

            container vpp-jvpp {
                uses config:service-ref {
                    refine type {
                        mandatory true;
                        config:required-identity vjvppc:vpp-jvpp;
                    }
                }
            }

            container classify-table-context {
                uses config:service-ref {
                    refine type {
                        mandatory true;
                        config:required-identity vpp-u:naming-context;
                    }
                }
            }
        }
    }


    identity vpp-honeycomb-writer {
        base config:module-type;
        config:provided-service tapi:honeycomb-writer-factory;
    }

    augment "/config:modules/config:module/config:configuration" {
        case vpp-honeycomb-writer {
            when "/config:modules/config:module/config:type = 'vpp-honeycomb-writer'";

            container vpp-jvpp-writer {
                uses config:service-ref {
                    refine type {
                        mandatory true;
                        config:required-identity vjvppc:vpp-jvpp;
                    }
                }
            }

            container interface-context-vpp {
                uses config:service-ref {
                    refine type {
                        mandatory true;
                        config:required-identity vpp-u:naming-context;
                    }
                }
            }

            container bridge-domain-context-vpp {
                uses config:service-ref {
                    refine type {
                        mandatory true;
                        config:required-identity vpp-u:naming-context;
                    }
                }
            }
        }
    }

    identity interfaces-honeycomb-writer {
        base config:module-type;
        config:provided-service tapi:honeycomb-writer-factory;
    }

    augment "/config:modules/config:module/config:configuration" {
        case interfaces-honeycomb-writer {
            when "/config:modules/config:module/config:type = 'interfaces-honeycomb-writer'";

            container vpp-jvpp-ifc {
                uses config:service-ref {
                    refine type {
                        mandatory true;
                        config:required-identity vjvppc:vpp-jvpp;
                    }
                }
            }

            container interface-context {
                uses config:service-ref {
                    refine type {
                        mandatory true;
                        config:required-identity vpp-u:naming-context;
                    }
                }
            }

            container bridge-domain-context {
                uses config:service-ref {
                    refine type {
                        mandatory true;
                        config:required-identity vpp-u:naming-context;
                    }
                }
            }

            container classify-table-context {
                uses config:service-ref {
                    refine type {
                        mandatory true;
                        config:required-identity vpp-u:naming-context;
                    }
                }
            }

        }
    }

    identity vpp-classifier-honeycomb-writer {
        base config:module-type;
        config:provided-service tapi:honeycomb-writer-factory;
    }

    augment "/config:modules/config:module/config:configuration" {
        case vpp-classifier-honeycomb-writer {
            when "/config:modules/config:module/config:type = 'vpp-classifier-honeycomb-writer'";

            container vpp-jvpp {
                uses config:service-ref {
                    refine type {
                        mandatory true;
                        config:required-identity vjvppc:vpp-jvpp;
                    }
                }
            }

            container classify-table-context {
                uses config:service-ref {
                    refine type {
                        mandatory true;
                        config:required-identity vpp-u:naming-context;
                    }
                }
            }
        }
    }

    identity vpp-cfg-initializer {
        base config:module-type;
        config:provided-service init:cfg-initializer;
        config:java-name-prefix VppConfigurationInitializer;
    }

    augment "/config:modules/config:module/config:configuration" {
        case vpp-cfg-initializer {
            when "/config:modules/config:module/config:type = 'vpp-cfg-initializer'";

             container binding-data-broker {
                uses config:service-ref {
                    refine type {
                        mandatory true;
                        config:required-identity md-sal-binding:binding-async-data-broker;
                    }
                }
             }
        }
    }

    identity interfaces-cfg-initializer {
        base config:module-type;
        config:provided-service init:cfg-initializer;
        config:java-name-prefix InterfacesConfigurationInitializer;
    }

    augment "/config:modules/config:module/config:configuration" {
        case interfaces-cfg-initializer {
            when "/config:modules/config:module/config:type = 'interfaces-cfg-initializer'";

             container binding-data-broker {
                uses config:service-ref {
                    refine type {
                        mandatory true;
                        config:required-identity md-sal-binding:binding-async-data-broker;
                    }
                }
             }
        }
    }

    identity vpp-classifier-cfg-initializer {
        base config:module-type;
        config:provided-service init:cfg-initializer;
        config:java-name-prefix VppClassifierConfigurationInitializer;
    }

    augment "/config:modules/config:module/config:configuration" {
        case vpp-classifier-cfg-initializer {
            when "/config:modules/config:module/config:type = 'vpp-classifier-cfg-initializer'";

             container binding-data-broker {
                uses config:service-ref {
                    refine type {
                        mandatory true;
                        config:required-identity md-sal-binding:binding-async-data-broker;
                    }
                }
             }
        }
    }


}
