module vpp-japi-cfg {
    yang-version 1;
    namespace "urn:honeycomb:params:xml:ns:yang:vpp:japi:cfg";
    prefix "vjc";

    import config { prefix config; revision-date 2013-04-05; }

    description
        "This module contains the base YANG definitions for
         readers/writers plugged into a honeycomb";

    revision "2016-04-06" {
        description
            "Initial revision.";
    }

    identity vpp-japi {
        base "config:service-type";
        config:java-class org.openvpp.vppjapi.vppApi;
    }

    identity vpp-japi-impl {
        base config:module-type;
        config:provided-service vpp-japi;
    }

    augment "/config:modules/config:module/config:configuration" {
        case vpp-japi-impl {
            when "/config:modules/config:module/config:type = 'vpp-japi-impl'";

            leaf name {
                type string;
                default "v3poODL";
            }
        }
    }

}
