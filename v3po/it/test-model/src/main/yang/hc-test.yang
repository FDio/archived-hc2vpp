module hc-test {
  yang-version 1;
  namespace "urn:opendaylight:params:xml:ns:yang:hc:test";
  prefix "hct";

  revision "2015-01-05" {
    description "Testing HC model with bindings";
  }

  import yang-ext {
    prefix "ext";
  }

  // WRITE ORDER 3
  // READ ORDER 1
  container simple-container {
    leaf simple-container-name {
      type string;
    }
  }

  grouping some-attributes {
    leaf leaf-from-grouping {
        type string;
    }

    // WRITE ORDER 5
    container container-from-grouping {
        leaf leaf-in-container-from-grouping {
            type int32;
        }
    }
  }

  // WRITE ORDER 9 (no real attributes though)
  // READ ORDER 2
  container container-with-list {
    // WRITE ORDER 7
    // READ ORDER 2.1
    list list-in-container {
        key "id";
        ordered-by "user";

        leaf id {
            type uint32;
        }

        // WRITE ORDER 8
        // READ ORDER 2.1.1
        container container-in-list {
            leaf name {
                type string;
            }

            // WRITE ORDER 6
            // READ ORDER 2.1.1.1
            list nested-list {
                key "nested-id";
                ordered-by "user";

                leaf nested-id {
                    type string;
                }

                leaf nested-name {
                    type string;
                }
            }
        }
    }
  }

  // WRITE ORDER 4
  container container-with-choice {
    leaf name {
        type string;
    }

    uses some-attributes;

    choice choice {
        leaf c1 {
            type string;
        }

        leaf c2 {
            type string;
        }

        // WRITE ORDER: 2
        container c3 {
            leaf name {
                type string;
            }
        }
    }
  }

  // WRITE ORDER: 2
  // READ ORDER 1.1
  augment "/hct:simple-container" {
    ext:augment-identifier "simple-augment";

    leaf simple-augment-leaf {
        type string;
    }
  }

  // WRITE UNORDERED
  // READ ORDER 1.2
  augment "/hct:simple-container" {
    ext:augment-identifier "complex-augment";

    // WRITE ORDER: 1
    // READ ORDER 1.2.1
    container complex-augment-container {
        leaf some-leaf {
            type string;
        }
    }
  }

}
