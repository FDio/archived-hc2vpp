module test-diff {
    yang-version 1;
    namespace "urn:opendaylight:params:xml:ns:yang:test:diff";
    prefix "td";

    revision "2015-01-05" {
        description "Initial revision";
    }

    container top-container {
        leaf string {
            type string;
        }

        list nested-list {
            key "name";

            leaf name {
                type string;
            }

            leaf text {
                type string;
            }

            list deep-list {
                key "name";

                leaf name {
                    type string;
                }

            }
        }
    }

    container with-choice {

        choice choice {
            case case1 {
                leaf in-case1 {
                    type string;
                }
            }

            case case2 {
                leaf in-case2 {
                    type string;
                }
            }
        }
    }

}
