module test-persistence {
    yang-version 1;
    namespace "urn:opendaylight:params:xml:ns:yang:test:persistence";
    prefix "tp";

    revision "2015-01-05" {
        description "Initial revision";
    }

    container top-container {
        leaf string {
            type string;
        }
    }

}
