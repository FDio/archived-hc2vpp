module translate-utils {
    yang-version 1;
    namespace "urn:honeycomb:params:xml:ns:yang:translate:utils";
    prefix "tutils";

    import config { prefix config; revision-date 2013-04-05; }
    import translate-api { prefix tapi; revision-date 2016-04-06; }
    import opendaylight-md-sal-binding { prefix md-sal-binding; revision-date 2013-10-28;}

    description
        "This module contains translation layer utilities";

    revision "2016-04-06" {
        description
            "Initial revision.";
    }

    identity delegating-reader-registry {
        base config:module-type;
        config:provided-service tapi:honeycomb-reader-registry;
        config:provided-service tapi:honeycomb-reader-registry-builder;
        config:java-name-prefix DelegatingReaderRegistry;
    }

    augment "/config:modules/config:module/config:configuration" {
        case delegating-reader-registry {
            when "/config:modules/config:module/config:type = 'delegating-reader-registry'";

                list reader-factory {
                    uses config:service-ref {
                        refine type {
                            mandatory true;
                            config:required-identity tapi:honeycomb-reader-factory;
                        }
                    }
                }

        }
    }

    identity delegating-writer-registry {
        base config:module-type;
        config:provided-service tapi:honeycomb-writer-registry;
        config:provided-service tapi:honeycomb-writer-registry-builder;
        config:java-name-prefix DelegatingWriterRegistry;
    }

    augment "/config:modules/config:module/config:configuration" {
        case delegating-writer-registry {
            when "/config:modules/config:module/config:type = 'delegating-writer-registry'";

                list writer-factory {
                    uses config:service-ref {
                        refine type {
                            mandatory true;
                            config:required-identity tapi:honeycomb-writer-factory;
                        }
                    }
                }

        }
    }

    identity noop-writer-registry-builder {
        base config:module-type;
        config:provided-service tapi:honeycomb-writer-registry-builder;
        config:java-name-prefix NoopWriterRegistry;
    }

    augment "/config:modules/config:module/config:configuration" {
        case noop-writer-registry-builder {
            when "/config:modules/config:module/config:type = 'noop-writer-registry-builder'";
        }
    }

    identity realtime-mapping-context {
        base config:module-type;
        config:provided-service tapi:honeycomb-mapping-context;
    }

    augment "/config:modules/config:module/config:configuration" {
        case realtime-mapping-context {
            when "/config:modules/config:module/config:type = 'realtime-mapping-context'";

            container context-binding-broker {
                uses config:service-ref {
                    refine type {
                        mandatory true;
                        config:required-identity md-sal-binding:binding-async-data-broker;
                    }
                }
            }
        }
    }
}
