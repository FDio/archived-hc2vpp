module vpp-routing-table-lookup {

    namespace "urn:ietf:params:xml:ns:yang:vpp-routing-table-lookup";
    prefix "vpp-routing";

    import vpp-routing {
        prefix "vpp-r";
    }

    organization
        "FD.io - The Fast Data Project";

    contact
        "Hc2vpp Wiki <https://wiki.fd.io/view/Hc2vpp>
         Mailing List <hc2vpp@lists.fd.io>";

    description
        "This module extends hc2vpp-ietf-routing module
         with VPP table lookup option.

         Copyright (c) 2017 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision 2017-09-17 {
        description "Initial revision";
    }

    grouping table-lookup-case-params {
        leaf secondary-vrf {
           type vpp-r:vni-reference;
           mandatory true;
           description "Secondary vrf used to lookup in";
        }
        // uses special deaggregation address every time : 0.0.0.0
    }

    //TODO - HONEYCOMB-398/HC2VPP-237 - move table lookup case here
}
