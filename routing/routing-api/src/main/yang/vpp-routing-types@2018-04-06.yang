module vpp-routing-types {

    namespace "http://fd.io/hc2vpp/yang/vpp-routing-types";
    prefix "vpp-routing-types";

    organization
        "FD.io - The Fast Data Project";

    contact
        "Hc2vpp Wiki <https://wiki.fd.io/view/Hc2vpp>
         Mailing List <hc2vpp@lists.fd.io>";

    description
        "This module contains a collection of YANG definitions
         that extend hc2vpp-ietf-routing-types module
         with VPP specific data.

         Copyright (c) 2018 Bell Canada, Pantheon Technologies and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision 2018-04-06 {
        description "Initial revision.";
    }

    import vpp-fib-table-management {
        prefix fib-management;
        revision-date 2018-05-21;
    }

    /*** Groupings ***/

    grouping vpp-next-hop-attributes {
        leaf weight{
            type uint8;
            description "Weight classification for next hop in list of next hops";
        }
    }

    grouping table-lookup-case-params {
        leaf secondary-vrf {
            type fib-management:fib-table-list-ref;
            mandatory true;
            description "Secondary vrf used to lookup in";
        }
        leaf address-family {
            type fib-management:address-family-type;
            description "Address family reference for secondary vrf.";
        }
        // uses special deaggregation address every time : 0.0.0.0
    }
}
