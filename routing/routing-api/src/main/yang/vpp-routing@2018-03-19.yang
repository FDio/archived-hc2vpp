module vpp-routing {

    namespace "http://fd.io/hc2vpp/yang/vpp-routing";
    prefix "vpp-routing";

    import yang-ext {
        prefix "ext";
    }

    import vpp-classifier {
        prefix "classifier";
    }

    import hc2vpp-ietf-routing {
        prefix "ietf-r";
        revision-date 2018-03-13;
    }

    import vpp-fib-table-management {
        prefix fib-management;
        revision-date 2018-05-21;
    }

    organization
        "FD.io - The Fast Data Project";

    contact
        "Hc2vpp Wiki <https://wiki.fd.io/view/Hc2vpp>
         Mailing List <hc2vpp@lists.fd.io>";

    description
        "This module contains a collection of YANG definitions
         that extend hc2vpp-ietf-routing module
         with VPP specific routing features.

         Copyright (c) 2016-2017 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision 2018-03-19 {
        description "Update hc2vpp-ietf-routing revision-date to 2018-03-13";
    }

    revision 2017-09-17 {
        description "Support for table lookup option moved to separate model.";
    }

    revision 2016-12-14 {
        description "Initial revision.";
    }

    grouping vpp-route-attributes {
        leaf classify-table{
        // classify_table_index + is_classify flag
            type classifier:classify-table-ref;
            description "Optional reference to classify table";
        }
    }

    grouping vpp-routing-protocol-attributes{
        //vrf_id
        leaf primary-vrf{
            type fib-management:fib-table-list-ref;
            mandatory true;
            description "Main vrf associated to route";
        }
        leaf address-family {
            type fib-management:address-family-type;
            description "Address family reference for primary vrf.";
        }
    }

    augment /ietf-r:routing/ietf-r:control-plane-protocols/ietf-r:control-plane-protocol{
        ext:augment-identifier "routing-protocol-vpp-attr";
        container vpp-protocol-attributes {
            presence "Config attributes";
            uses vpp-routing-protocol-attributes;
        }
    }
}
