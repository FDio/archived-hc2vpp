module vpp-routing {

    namespace "urn:ietf:params:xml:ns:yang:vpp-routing";
    prefix "vpp-routing";

    import yang-ext {
        prefix "ext";
    }

    import vpp-classifier {
        prefix "classifier";
    }

    import hc2vpp-ietf-routing {
        prefix "ietf-r";
    }

    organization
        "FD.io - The Fast Data Project";

    contact
        "Hc2vpp Wiki <https://wiki.fd.io/view/Hc2vpp>
         Mailing List <hc2vpp@lists.fd.io>";

    description
        "This module contains a collection of YANG definitions
         that extend hc2vpp-ietf-routing module
         with VPP specific routing features.

         Copyright (c) 2016-2017 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision 2017-09-17 {
        description "Support for table lookup option moved to separate model.";
    }

    revision 2016-12-14 {
        description "Initial revision.";
    }

    typedef vni-reference{
        type uint32;
        description "Vrf index reference";
    }

    grouping vpp-route-attributes {
        leaf classify-table{
        // classify_table_index + is_classify flag
            type classifier:classify-table-ref;
            description "Optional reference to classify table";
        }
    }

    grouping vpp-routing-protocol-attributes{
        //vrf_id
        leaf primary-vrf{
            type vni-reference;
            mandatory true;
            description "Main vrf associated to route";
        }
    }

    augment /ietf-r:routing/ietf-r:routing-instance/ietf-r:routing-protocols/ietf-r:routing-protocol{
        ext:augment-identifier "routing-protocol-vpp-attr";
        container vpp-protocol-attributes {
            presence "Config attributes";
            uses vpp-routing-protocol-attributes;
        }
    }

    augment /ietf-r:routing-state/ietf-r:routing-instance/ietf-r:routing-protocols/ietf-r:routing-protocol{
        ext:augment-identifier "routing-protocol-state-vpp-attr";
        container vpp-protocol-state-attributes {
            presence "Operational attributes";
            uses vpp-routing-protocol-attributes;
        }
    }
}
