module dhcp {
    yang-version 1;
    namespace "urn:opendaylight:params:xml:ns:yang:vpp:dhcp";
    prefix "dhcp";

    import ietf-inet-types {
        prefix inet;
    }

    organization
        "FD.io - The Fast Data Project";

    contact
        "Hc2vpp Wiki <https://wiki.fd.io/view/Hc2vpp>
         Mailing List <hc2vpp@lists.fd.io>";

    description
        "This module contains a collection of YANG definitions for
         managing DHCP in VPP.

         Copyright (c) 2017-2018 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision "2018-01-03" {
        description
            "Changes type of ip-addresses from inet:ip-address to inet:ip-address-no-zone.";
        reference
            "https://jira.fd.io/browse/HC2VPP-79";
    }

    revision "2017-03-15" {
        description
            "Initial revision of dhcp model";
    }

    identity address-family {
        description
            "Base identity from which identities describing address
            families are derived.";
    }

    identity ipv4 {
        base address-family;
        description
            "This identity represents IPv4 address family.";
    }

    identity ipv6 {
        base address-family;
        description
            "This identity represents IPv6 address family.";
    }

    typedef address-type {
        type identityref {
            base address-family;
        }
    }

    grouping relay-attributes {
        list server {
          key "vrf-id address";
          leaf address {
            type inet:ip-address-no-zone;
            description
              "IP address of the server DHCP packets will be forwarded to.";
          }
          leaf vrf-id {
            type uint32;
            description
              "Used to send DHCP messages to the server";
          }
        }

        leaf gateway-address {
          type inet:ip-address-no-zone;
            mandatory true;
            description
                "IP address of the relay agent.";
        }
        // TODO(HC2VPP-44): add configurable circut-id (option-82/remote-id)
    }

    grouping dhcp-attributes {
        container relays {
            list relay {
                key "address-type rx-vrf-id";
                leaf address-type {
                    type address-type;
                }
                leaf rx-vrf-id {
                    type uint32;
                    description
                        "Used to receive DHCP messages from clients.";
                }
                uses relay-attributes;
            }
        }
    }

    container dhcp {
        uses dhcp-attributes;
    }
}
