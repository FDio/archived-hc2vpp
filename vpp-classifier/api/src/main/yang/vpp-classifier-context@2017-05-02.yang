module vpp-classifier-context {
  yang-version 1;
  namespace "http://fd.io/hc2vpp/yang/vpp-classifier-context";
  prefix "vpp-classifier-context";

  organization
    "FD.io - The Fast Data Project";

  contact
    "Hc2vpp Wiki <https://wiki.fd.io/view/Hc2vpp>
     Mailing List <hc2vpp@lists.fd.io>";

  description
    "This module provides metadata required for vpp-classifier management.

     Metadata are managed internally by the HC vpp-classifier plugin.
     They are exposed as operational state data for debugging purposes.

     Copyright (c) 2016-2017 Cisco and/or its affiliates.

     Licensed under the Apache License, Version 2.0 (the 'License');
     you may not use this file except in compliance with the License.
     You may obtain a copy of the License at:

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision "2017-05-02" {
    description "Changed namespace";
  }

  revision "2016-09-09" {
    description
      "Initial revision.";
  }

  container vpp-classifier-context {

    config "false";

    description
      "Classify tables and sessions contain relative node indexes. Management agent like Honeycomb,
       needs to use node names instead (indexes might change after vpp restart).
       VPP does not provide relative index to node name conversion (https://jira.fd.io/browse/VPP-219),
       also finding base node that is needed to perform the conversion
       is not allways possible (https://jira.fd.io/browse/VPP-220).

       Therefore Honeycomb needs to provide relative node to index mapping.";

    list classify-table-context {
      key "name";
      unique "index";

      leaf name {
        type string;
        description
          "Name of the classify table.";
      }

      leaf index {
        type int32;
        description
          "Classify table index used by VPP.";
      }

      leaf classifier-node-name {
        type string;
        description
          "Name of VPP node the table is defined for.";
      }

      list node-context {
        key "name";
        unique "index";

        leaf name {
          type string;
          description
            "Name of vpp node (neighbour of classifier-node-name)";
        }

        leaf index {
          type int32;
          description
            "Inted of the vpp node relative to classifier-node-name";
        }
      }
    }
  }
}
