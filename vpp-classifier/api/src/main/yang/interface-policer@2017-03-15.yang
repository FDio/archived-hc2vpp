module interface-policer {

    yang-version 1;
    namespace "http://fd.io/hc2vpp/yang/interface-policer";
    prefix "ifc-policer";

    import vpp-classifier {
        prefix "vpp-classifier";
    }

    import ietf-interfaces {
        prefix "if";
    }

    import yang-ext {
        prefix "ext";
    }

    organization
        "FD.io - The Fast Data Project";

    contact
        "Hc2vpp Wiki <https://wiki.fd.io/view/Hc2vpp>
         Mailing List <hc2vpp@lists.fd.io>";

    description
        "This YANG module defines policer configuration and
         operational data for interfaces in VPP.
         Mapped to policer_classify_set_interface:
         https://git.fd.io/vpp/tree/src/vnet/classify/classify.api#n119.

         Copyright (c) 2017 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision "2017-03-15" {
        description "Initial revision of interface-policer model";
    }

    grouping interface-policer-attributes {
        container policer {
            description
                "Defines references to policer classify tables.
                 At least one table reference should be specified.";
            leaf l2-table {
                type vpp-classifier:classify-table-ref;
                description
                    "An L2 policer table";
            }
            leaf ip4-table {
                type vpp-classifier:classify-table-ref;
                description
                    "An IPv4 policer table";
            }
            leaf ip6-table {
                type vpp-classifier:classify-table-ref;
                description
                    "An IPv6 policer table";
            }
        }
    }

    augment /if:interfaces/if:interface {
        ext:augment-identifier "policer-interface-augmentation";

        uses interface-policer-attributes;
    }
}
