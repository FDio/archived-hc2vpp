module vpp-subinterface-acl {
    yang-version 1;
    namespace "urn:opendaylight:params:xml:ns:yang:vpp:subinterface:acl";
    prefix "vpp-subifc-acl";

    revision "2017-03-15" {
        description
            "Initial revision of vpp-subinterface-acl model.";
    }

    import ietf-interfaces {
        prefix "if";
    }

    import vpp-vlan {
        prefix "vpp-vlan";
    }

    import vpp-classifier-acl {
        prefix "vpp-classifier-acl";
    }

    import yang-ext {
        prefix "ext";
    }

    augment /if:interfaces/if:interface/vpp-vlan:sub-interfaces/vpp-vlan:sub-interface {
       ext:augment-identifier "vpp-subinterface-acl-augmentation";
       uses vpp-classifier-acl:vpp-acl-attributes;
    }

    augment /if:interfaces-state/if:interface/vpp-vlan:sub-interfaces/vpp-vlan:sub-interface {
       ext:augment-identifier "vpp-subinterface-acl-state-augmentation";
       uses vpp-classifier-acl:vpp-acl-attributes;
    }
}
