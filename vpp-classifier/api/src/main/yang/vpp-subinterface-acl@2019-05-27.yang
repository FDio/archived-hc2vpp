module vpp-subinterface-acl {
    yang-version 1;
    namespace "http://fd.io/hc2vpp/yang/vpp-subinterface-acl";
    prefix "vpp-subifc-acl";

    import ietf-interfaces {
        prefix "if";
    }

    import vpp-vlan {
        prefix "vpp-vlan";
    }

    import vpp-classifier-acl {
        prefix "vpp-classifier-acl";
    }

    import yang-ext {
        prefix "ext";
    }

    organization
        "FD.io - The Fast Data Project";

    contact
        "Hc2vpp Wiki <https://wiki.fd.io/view/Hc2vpp>
         Mailing List <hc2vpp@lists.fd.io>";

    description
        "This module contains a collection of YANG definitions for
         applying ACLs on VPP sub-interfaces.
         Uses ACL implementation based on VPP packet classifier.

         Copyright (c) 2017 Cisco and/or its affiliates.

         Licensed under the Apache License, Version 2.0 (the 'License');
         you may not use this file except in compliance with the License.
         You may obtain a copy of the License at:

         http://www.apache.org/licenses/LICENSE-2.0

         Unless required by applicable law or agreed to in writing, software
         distributed under the License is distributed on an 'AS IS' BASIS,
         WITHOUT WARRANTIES OR CONDITIONS OF ANY KIND, either express or implied.
         See the License for the specific language governing permissions and
         limitations under the License.";

    revision "2019-05-27" {
        description
            "Removed interfaces-state augmentations due to its deprecation
             in ietf-interfaces model";
    }

    revision "2017-03-15" {
        description
            "Initial revision of vpp-subinterface-acl model.";
    }

    augment /if:interfaces/if:interface/vpp-vlan:sub-interfaces/vpp-vlan:sub-interface {
       ext:augment-identifier "vpp-subinterface-acl-augmentation";
       uses vpp-classifier-acl:vpp-acl-attributes;
    }
}
